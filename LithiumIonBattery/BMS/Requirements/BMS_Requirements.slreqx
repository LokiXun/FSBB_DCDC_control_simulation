# BMS_Requirements

## BMS_Requirements: References to BMS_Requirements.docx (Container)
Read-only references to Microsoft Word document.

### 1 Overview: Overview (Functional)
1 Overview
This document describes a requirement specification for Battery Management System (BMS). The BMS system provides functionalities to control the battery pack.

### 2 BMS Interfaces: BMS Interfaces (Functional)
2 BMS Interfaces

#### 2.1 BMS Inputs: BMS Inputs (Functional)
2.1 BMS Inputs
| Name | Data type | Units | From |
| --- | --- | --- | --- |
| StateRequest | enum | / | CAN |
| Cell_Voltages | single | V | Sensors |
| Cell_Temperatures | single | K | Sensors |
| Pack_Voltage | single | V | Sensors |
| Pack_Current | single | A | Sensors |
| Vout_Chgr | single | V | Sensors |
| Vout_Invtr | single | V | Sensors |

##### 2.1.1 Cell_Voltages: Cell_Voltages (Functional)
2.1.1 Cell_Voltages
BMS shall measure voltage across each cell block (cells in series) at sample rate of 10Hz.

##### 2.1.2 Cell_Temperatures: Cell_Temperatures (Functional)
2.1.2 Cell_Temperatures
BMS shall measure battery cell Temperatures (Cell_Temperatures)

##### 2.1.3 Pack_Current: Pack_Current (Functional)
2.1.3 Pack_Current
BMS shall measure current flowing through battery pack at sample rate of 10Hz. Pack_Current > 0 indicates battery pack charging. Pack_Current < 0 indicates battery pack discharging.

##### 2.1.4 Pack_Voltage: Pack_Voltage (Functional)
2.1.4 Pack_Voltage
BMS shall measure voltage across Pack terminals (+Ve Batt and -Ve Batt) at sample rate of 10Hz.

##### 2.1.5 Vout_Chgr: Vout_Chgr (Functional)
2.1.5 Vout_Chgr
BMS shall measure terminal voltage at charger contactor (Vout_Chgr).

##### 2.1.6 Vout_Invtr: Vout_Invtr (Functional)
2.1.6 Vout_Invtr
BMS shall measure terminal voltage at Inverter contactor (Vout_Invtr)

##### 2.1.7 StateRequest: StateRequest (Functional)
2.1.7 StateRequest
BMS shall read State Request from CAN Bus (StateRequest)

#### 2.2 BMS Outputs: BMS Outputs (Functional)
2.2 BMS Outputs
| Name | Data type | Units | To |
| --- | --- | --- | --- |
| SOC | boolean | % | CAN |
| BMS_State | boolean | enum | CAN |
| Current Limits | single | A | Other BMS modules / Plant (DriveLoad) |
| BalCmd | boolean | / | Plant (DriveLoad) |
| ChargeCurrentReq | boolean | / | Plant (Charger) |
| PosContactorChgrCmd | boolean | / | Plant (BatteryPack CellMonitoring) |
| PreChargeRelayChgrCmd | boolean | / | Plant (BatteryPack CellMonitoring) |
| NegContactorChgrCmd | boolean | / | Plant (BatteryPack CellMonitoring) |
| PosContactorInvtrCmd | boolean | / | Plant (BatteryPack CellMonitoring) |
| PreChargeRelayInvtrCmd | boolean | / | Plant (BatteryPack CellMonitoring) |
| NegContactorInvtrCmd | boolean | / | Plant (BatteryPack CellMonitoring) |

##### 2.2.1 SOC: SOC (Functional)
2.2.1 SOC
State of Charge

##### 2.2.2 BMS_State: BMS_State (Functional)
2.2.2 BMS_State
(State: Standby-Charging-Discharging-Fault)

##### 2.2.3 Current Limits: Current Limits (Functional)
2.2.3 Current Limits
(Limits for Charge and Discharge

##### 2.2.4 BalCmd: BalCmd (Functional)
2.2.4 BalCmd
(Command to balance the battery cells)

##### 2.2.5 ChargeCurrentReq: ChargeCurrentReq (Functional)
2.2.5 ChargeCurrentReq
(Current request during charging)

##### 2.2.6 PosContactorChgrCmd (: PosContactorChgrCmd ( (Functional)
2.2.6 PosContactorChgrCmd (
Command for contactor on the Positive pole of the charger)

##### 2.2.7 PreChargeRelayChgrCmd: PreChargeRelayChgrCmd (Functional)
2.2.7 PreChargeRelayChgrCmd
(Command for contactor for pre-charge of the charger)

##### 2.2.8 NegContactorChgrCmd: NegContactorChgrCmd (Functional)
2.2.8 NegContactorChgrCmd
(Command for contactor on the Negative pole of the charger)

##### 2.2.9 PosContactorInvtrCmd: PosContactorInvtrCmd (Functional)
2.2.9 PosContactorInvtrCmd
(Command for contactor on the Positive pole of the inverter)

##### 2.2.10 PreChargeRelayInvtrCmd: PreChargeRelayInvtrCmd (Functional)
2.2.10 PreChargeRelayInvtrCmd
(Command for contactor for pre-charge of the inverter)

##### 2.2.11 NegContactorInvtrCmd: NegContactorInvtrCmd (Functional)
2.2.11 NegContactorInvtrCmd
Command for contactor on the Positive pole of the Inverter)

### 3 BMS Architecture and module specifications: BMS Architecture and module specifications (Functional)
3 BMS Architecture and module specifications
BMS software must be divided in 4 modules:
1. Main State Machine
2. Current Power Limits Calculation
3. SOC Estimation
4. Balancing Logic
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
#### 3.1 BMS - Main State Machine: BMS - Main State Machine (Functional)
3.1 BMS - Main State Machine
The Main State Machine has 4 main functionalities:
· Manage the BMS status evolution on driving requests and safety
· Calculate the correct charging mode
· Monitors current, voltage and temperature faults for safety
· Securely close and open the contacts to the charger e inverter
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
##### 3.1.1 BMS Main State Machine: Interfaces: BMS Main State Machine: Interfaces (Functional)
3.1.1 BMS Main State Machine: Interfaces

###### 3.1.1.1 Inputs: Inputs (Functional)
3.1.1.1 Inputs
| Name | Data type | Units | From |
| --- | --- | --- | --- |
| StateRequest | enum | / | CAN |
| Cell_Voltages | single | V | Sensors |
| Cell_Temperatures | single | K | Sensors |
| Pack_Voltage | single | V | Sensors |
| Pack_Current | single | A | Sensors |
| Vout_Chgr | single | V | Sensors |
| Vout_Invtr | single | V | Sensors |
| Current Limits | single | A | Other BMS modules |
| Max Cell Voltage | single | V | From other BMS modules |
| Min Cell Voltage | single | V | From other BMS modules |

###### 3.1.1.2 Outputs: Outputs (Functional)
3.1.1.2 Outputs
| Name | Data type | Units | To |
| --- | --- | --- | --- |
| BMS_State | boolean | enum | CAN & other modules |
| ChargeCurrentReq | boolean | / | Plant (Charger) |
| PosContactorChgrCmd | boolean | / | Plant (BatteryPack CellMonitoring) |
| PreChargeRelayChgrCmd | boolean | / | Plant (BatteryPack CellMonitoring) |
| NegContactorChgrCmd | boolean | / | Plant (BatteryPack CellMonitoring) |
| PosContactorInvtrCmd | boolean | / | Plant (BatteryPack CellMonitoring) |
| PreChargeRelayInvtrCmd | boolean | / | Plant (BatteryPack CellMonitoring) |
| NegContactorInvtrCmd | boolean | / | Plant (BatteryPack CellMonitoring) |

##### 3.1.2 BMS Main State Machine: BMS State calculation: BMS Main State Machine: BMS State calculation (Functional)
3.1.2 BMS Main State Machine: BMS State calculation
It is necessary to switch appropriately the BMS Mode (Standby, Charging, Driving, State) based on State Request, Relay Contactors States (charger and Inverter), Fault

##### 3.1.3 BMS Main State Machine: Charging Mode calculation: BMS Main State Machine: Charging Mode calculation (Functional)
3.1.3 BMS Main State Machine: Charging Mode calculation
It is necessary to switch appropriately the Charge Mode (Init, Costant Current (CC) Mode, Costant Voltage (CV) Mode)

##### 3.1.4 BMS Main State Machine: Relay Charger Commands: BMS Main State Machine: Relay Charger Commands (Functional)
3.1.4 BMS Main State Machine: Relay Charger Commands
It is necessary to open and close appropriately the Relays (Pre-charger, Positive and Negative) for the Charger

##### 3.1.5 BMS Main State Machine: Relay Inverter Commands: BMS Main State Machine: Relay Inverter Commands (Functional)
3.1.5 BMS Main State Machine: Relay Inverter Commands
It is necessary to open and close appropriately the Relays (Pre-charger, Positive and Negative) for the Inverter

##### 3.1.6 BMS Main State Machine: Fault Monitor Calculation: BMS Main State Machine: Fault Monitor Calculation (Functional)
3.1.6 BMS Main State Machine: Fault Monitor Calculation

###### 3.1.6.1 Current Limitation: Current Limitation (Functional)
3.1.6.1 Current Limitation
It is necessary detect the Over Current Pack Fault

###### 3.1.6.2 Temperature Limitation: Temperature Limitation (Functional)
3.1.6.2 Temperature Limitation
It is necessary detect the High and Low Cell Temperature Fault

###### 3.1.6.3 Voltage Limitation: Voltage Limitation (Functional)
3.1.6.3 Voltage Limitation
It is necessary detect the Over and Under Voltage Temperature Fault

#### 3.2 BMS – Current Limit Calculation: BMS – Current Limit Calculation (Functional)
3.2 BMS – Current Limit Calculation
The Current Limit Calculation must calculate Minimum and Maximum Cell Voltage and the Current limits
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
##### 3.2.1 BMS Current Limit Calculation: Interfaces: BMS Current Limit Calculation: Interfaces (Functional)
3.2.1 BMS Current Limit Calculation: Interfaces

###### 3.2.1.1 Inputs: Inputs (Functional)
3.2.1.1 Inputs
| Name | Data type | Units | Description |
| --- | --- | --- | --- |
| Cell_Voltages | single | V | Sensors |

###### 3.2.1.2 Outputs: Outputs (Functional)
3.2.1.2 Outputs
| Name | Data type | Units | to |
| --- | --- | --- | --- |
| Current Limits | single | A | Other BMS modules / Plant (DriveLoad) |
| Max Cell Voltage | single | V | Other BMS modules |
| Min Cell Voltage | single | V | Other BMS modules |

##### 3.2.4 BMS Current Limit Calculation: C: BMS Current Limit Calculation: Charge Current Limit (Functional)
3.2.4 BMS Current Limit Calculation: Charge Current Limit
Calculate the charge current limit following Software requirements

##### 3.2.2 BMS Current Limit Calculation: Min/Max Calculation: BMS Current Limit Calculation: Min/Max Calculation (Functional)
3.2.2 BMS Current Limit Calculation: Min/Max Calculation
Calculation of Max and Min Voltage between cells

##### 3.2.3 BMS Current Limit Calculation: D: BMS Current Limit Calculation: Discharge Current Limit (Functional)
3.2.3 BMS Current Limit Calculation: Discharge Current Limit
Calculate the discharge current limit following Software requirements

#### 3.3 BMS – SOC Estimation: BMS – SOC Estimation (Functional)
3.3 BMS – SOC Estimation
The SOC Estimation must calculate SOC estimation (SOC_CC, SOC_UKF, SOC_EKF)
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
##### 3.3.1 BMS SOC Estimation: Interfaces: BMS SOC Estimation: Interfaces (Functional)
3.3.1 BMS SOC Estimation: Interfaces

###### 3.3.1.1 Inputs: Inputs (Functional)
3.3.1.1 Inputs
| Name | Data type | Units | From |
| --- | --- | --- | --- |
| Pack_Current | single | A | Sensors |
| Cell_Temperatures | single | K | Sensors |
| Cell_Voltages | single | V | Sensors |

###### 3.3.1.2 Outputs: Outputs (Functional)
3.3.1.2 Outputs
| Name | Data type | Units | To |
| --- | --- | --- | --- |
| SOCs | % | / | CAN |

##### 3.3.2 BMS SOC Estimation: Coulomb Counting: BMS SOC Estimation: Coulomb Counting (Functional)
3.3.2 BMS SOC Estimation: Coulomb Counting
Calculate the SOC with Coulomb Counting following Software requirements

##### 3.3.3 BMS SOC Estimation: SOC UKF: BMS SOC Estimation: SOC UKF (Functional)
3.3.3 BMS SOC Estimation: SOC UKF
Calculate the SOC with UKF following Software requirements

##### 3.3.4 BMS SOC Estimation: SOC EKF: BMS SOC Estimation: SOC EKF (Functional)
3.3.4 BMS SOC Estimation: SOC EKF
Calculate the SOC with EKF following Software requirements

#### 3.4 BMS – Balancing Logic: BMS – Balancing Logic (Functional)
3.4 BMS – Balancing Logic
The Balancing Logic must securely close and open the contacts to the charger e inverter
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
##### 3.4.1 BMS Balancing Logic Interfaces: BMS Balancing Logic Interfaces (Functional)
3.4.1 BMS Balancing Logic Interfaces

###### 3.4.1.1 Inputs: Inputs (Functional)
3.4.1.1 Inputs
| Name | Data type | Units | From |
| --- | --- | --- | --- |
| BMS_State | boolean | enum | Other modules |
| Cell_Voltages | single | V | Sensors |
| Max Cell Voltage | single | V | Other BMS modules |
| Min Cell Voltage | single | V | Other BMS modules |

###### 3.4.1.2 Outputs: Outputs (Functional)
3.4.1.2 Outputs
| Name | Data type | Units | To |
| --- | --- | --- | --- |
| BalCmd | boolean | / | Plant (DriveLoad) |

##### 3.4.2 BMS Balancing Logic: Balancing ON/OFF: BMS Balancing Logic: Balancing ON/OFF (Functional)
3.4.2 BMS Balancing Logic: Balancing ON/OFF
Calculate if perform balancing

##### 3.4.3 BMS Balancing Logic: Contacts Co: BMS Balancing Logic: Contacts Command calculation & Deactivation (Functional)
3.4.3 BMS Balancing Logic: Contacts Command calculation & Deactivation
Calculate the commands for inverter and charger contactors
