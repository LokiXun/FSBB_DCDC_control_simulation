# StateMachine_Requirements

## #7: Inputs (Functional)

### #8: StateRequest (Functional)
Data type: enum: SRE(Balancing = 0, Charging = 1, Driving = 2)
Unit: /
Min: 0
Max: 2

### #9: Cell_Voltages (Functional)
Data type: single
Unit: V
Min: 0
Max 5:
Dimension: # Cells

### #10: Cell_Temperatures (Functional)
Data type: single
Unit: K
Min: 263,15
Max:333.15
Dimension: # Cells

### #11: Pack_Voltage (Functional)
Data type: single
Unit: V
Min: 0
Max: 480

### #12: Pack_Current (Functional)
Data type: single
Unit: A
Min: - 100
Max: 100

### #13: Vout_Chgr (Functional)
Data type: single
Unit: V
Min: -500
Max: 500

### #14: Vout_Invrt (Functional)
Data type: single
Unit: V
Min: -500
Max: 500

### #15: Current_Limits (Functional)
Data type: Bus:CurrentLimits
Unit: A
Min:
Max:

### #16: MaxCellVolt (Functional)
Data type: single
Unit: V
Min: 0
Max: 5

### #17: MinCellVolt (Functional)
Data type: single
Unit: V
Min: 0
Max: 5

## #18: Outputs (Functional)

### #20: BMS_State (Functional)
Data type: Enum
Unit: /
Min:
Max:

### #21: ChargeCurrentReq (Functional)
Data type: single
Unit: A
Min: -100
Max: 100

### #22: PosContactorChgrCmd (Functional)
Data type: bool
Unit: /
Min: 0
Max: 1

### #23: PreChargeRelayChgrCmd (Functional)
Data type: bool
Unit: /
Min: 0
Max: 1

### #24: NegContactorChgrCmd (Functional)
Data type: bool
Unit:
Min: 0
Max: 1

### #25: PosContactorInvtrCmd (Functional)
Data type: bool
Unit: /
Min: 0
Max: 1

### #26: PreChargeRelayInvtrCmd (Functional)
Data type: bool
Unit: /
Min: 0
Max: 1

### #27: NegContactorInvtrCmd (Functional)
Data type: bool
Unit: /
Min: 0
Max: 1

### #28: Faults (Functional)
Data type: bool
Unit: Bus
Min: 0
Max: 1

## #29: Overview (Functional)
The Main State Machine has 4 main functionalities:
· Manage the BMS status evolution on driving requests and safety
· Calculate the correct charging mode
· Monitors current, voltage and temperature faults for safety
· Securely close and open the contacts to the charger e inverter

## #30: State Machine Architecture (Functional)

### #31: BMS State and Charging Mode calculation (Functional)
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It is necessary to switch appropriately the BMS Mode (Standby, Charging, Driving, State) based on State Request, Relay Contactors States (charger and Inverter), Fault. Furthermore it is necessary to request appropriately the charging mode
BMS Mode can have the following Values:
- BMS_Standby
- BMS_Driving
- BMS_Charging
- BMS_Fault
The initial BMS Mode is BMS_Standby
Charging Mode can have the following Values:
- CC Mode (Constant Current)
- CV Mode (Constant Voltage)

#### #32: BMS State in Standby (Functional)
When in Standby State the BMS_State is = BMS_Standby

##### #45: Exit Conditions and Priorities (Functional)
Priory Exits:
- to Fault
- to Charging
- to Driving

###### #33: Exit conditions to BMS State Charging (Functional)
if State Request is Charging and Charging contactors are closed

###### #34: Exit conditions to BMS State Driving (Functional)
if State Request is Driving and Inverter contactors are closed

###### #36: Exit conditions to BMS State Fault (Functional)
if Fault is present

#### #39: BMS State in Driving (Functional)
When in Standby State the BMS_State is = BMS_Driving

##### #51: Exit Conditions and Priorities (Functional)
Priory Exits:
- to Fault
- to Charging
- to Standby

###### #40: Exit conditions to BMS State Standby (Functional)
if State Request is different from Driving and Inverter contactors are init

###### #41: Exit conditions to BMS State Charging (Functional)
if State Request is Charging and Charger contactors are closed

###### #42: Exit conditions to BMS State Fault (Functional)
if Fault is present

#### #48: Initial BMS Mode (Functional)
The initial BMS Mode is BMS_Standby

#### #52: BMS State in Charging (Functional)
When in Standby State the BMS_State is = BMS_Charging

##### #53: Exit Conditions and Priorities (Functional)
Priory Exits:
1) to Fault
2) to Driving
3) to Standby

###### #54: Exit conditions to BMS State Fault (Functional)
if Fault is present

###### #55: Exit conditions to BMS State Driving (Functional)
if State Request is Charging and Inverter contactors are Closed

###### #56: Exit conditions to BMS State Standby (Functional)
if State Request is diffrenet from Charging and Charging contactors are Init

##### #58: Charge Mode and Charge Current Request Calculation (Functional)
In Charging State there are 3 Charge mode states:
- Init
- CC (Constant Current)
- CV (Constant Voltage)

###### #59: Enter in Charging State (Functional)
Once enter in Charging state the initial Charge Mode is Init

###### #60: Init Charge Mode (Functional)
When in Init Charge Mode:
ChargeModeReq = No_Charging and
ChargeCurrentRequest = 0

###### #64: Exit to Charge CC (Functional)
if State Request is Charging and MaxCellVolt < Charging_CC_Threshold

###### #61: CC Charge Mode (Functional)
When in Init Charge Mode:
ChargeModeReq = CC_Charging and
ChargeCurrentRequest(z) = min(Icc, ChargeCurrentLimit)

###### #73: Exit Condition and Priorities (Functional)
Priory Exits:
1) Exit to Charge Init Mode
2) Exit to Charge CC Mode

###### #63: Exit to Charge Init (Functional)
if State Request is different from Charging

###### #74: Exit to Charge CC (Functional)
if State Request is Charging and MaxCellVolt >= MaxCellVoltThrsld

###### #62: CV Charge Mode (Functional)
When in Init Charge Mode:
ChargeModeReq = CV_Charging and
ChargeCurrentRequest(z) = min((ChargeCurrentReq(z-1) - CV_Gain*(MaxCellVolt - MaxCellVoltThrsld), ChargeCurrentLimit);

###### #68: Exit to Charge Init (Functional)
if State Request is different from Charging OR ChargeCurrentReq <= Icc/10

#### #57: BMS State in Fault (Functional)
When in Fault State the BMS_State is = BMS_Fault

### #76: BMS Fault Monitoring (Functional)
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It is necessary monitoring and limitate:
- Current
- Temperature
- Voltage
in the battery

#### #77: Current Limitation (Functional)
During Current monitoring there are 3 states:
- No Current Limitation
- Wait
- Over Current Fault

##### #78: Init State (Functional)
The initial state is No Current Limitation.
Before to enter in this state we set FaultPresent = false

##### #79: No Current Limitation State (Functional)

###### #80: Exit to Wait State (Functional)
If:
Package Current < Discharge Current Limit OR
Package Current > Charge Current Limit

##### #87: Wait State (Functional)

###### #81: Exit Condition and Priorities (Functional)
Priory Exits:
1) Exit to Over Current Fault
2) Exit to No Current Limitation

###### #82: Exit to Over Current Fault (Functional)
if WaitCurrentLimitationConf seconds elapse from entering the state

###### #83: Exit to No Current Limitation (Functional)
if:
Package Current >= Discharge Current Limit OR
Package Current <= Charge Current Limit

##### #88: Over Current Limitation (Functional)
In this state it is necessary set:
- FaultPresent = 1
- Fault_out.OverCurrent = 1;

#### #89: Temperature Fault (Functional)
During Temperature monitoring there are 3 states:
- No Temperature Fault
- High Temperature Fault
- Low Temperature Fault

##### #90: Init State (Functional)
The initial state is No Temperature Fault.
Before to enter in this state we set FaultPresent = false

##### #91: No Temperature Fault State (Functional)
During No Temperature Fault the following values are calculated:
- MaxCellTemp = max(Cell_Temperatures)
- MinCellTemperatues = min(Cell_Temperatures)

###### #98: Exit Condition and Priorities (Functional)
Priory Exits:
1) Exit to High Temperature Fault
2) Exit to Low Temperature Fault

###### #99: Charger Contactor Management (Functional)
if MaxCellTemp >= HighTempLimit

###### #100: Exit to Low Tempearture Fault (Functional)
if MinCellTemp >= LowTempLimit

##### #93: High Tempearture Fault (Functional)
In this state set:
- FaultPresent = true
- Fault_out.HighTemp = 1;

##### #101: Low Tempearture Fault (Functional)
In this state set:
- FaultPresent = true
- Fault_out.MinTemp = 1;

#### #102: Voltage Fault (Functional)
During Voltage monitoring there are 4 states:
- No Voltage Fault
- Over Voltage Fault
- Under Voltage Fault
- Sensor Voltage Fault

##### #103: Init State (Functional)
The initial state is No Voltage Fault.
Before to enter in this state we set FaultPresent = false

##### #104: No Voltage Fault State (Functional)
During No Voltage Fault the following values are calculated:
- SumOfVoltages = max(Cell_Voltages)
- Delta = abs(Pack Voltage - SumOfVoltages)

###### #105: Exit Condition and Priorities (Functional)
Priory Exits:
1) Exit to Over Voltage Fault
2) Exit to Under Voltage Fault
3) Exit to Sensor Fault

###### #106: Exit to Over Voltage Fault (Functional)
if MaxCellVolt >= OverCellVoltageLimit

###### #107: Exit to Under Voltage Fault (Functional)
if MinCellVolt <= UnderCellVoltageLimit

###### #110: Exit to Sensor Fault (Functional)
if Delta > SnsrFltThld

##### #108: Over Voltage Fault (Functional)
In this state set:
- FaultPresent = true
- Fault_out.OverVolt = 1;

##### #109: Under Voltage Fault (Functional)
In this state set:
- FaultPresent = true
- Fault_out.UnderVolt = 1;

##### #111: Sensor Fault (Functional)
In this state set:
- FaultPresent = true
- Fault_out.SensorVolt = 1;

### #112: Charger Contactors Management (Functional)
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It is necessary close and open charger contactors following some steps

#### #113: Opening (Functional)

##### #114: Init State (Functional)
The initial state is Open Pre-Charger Contactors.
Before to enter in this state we set Fault_out.Charger = false

##### #115: Open Positive Contactors (Functional)
In this state set Charger Command Positive Contactor = false

###### #116: Exit to Open Pre-Charger Contactors (Functional)
if ContactorTime seconds elapse from entering the state

##### #117: Close Pre-Charger Contactors (Functional)
In this state set Charger Command Pre-charger Contactor = true

###### #119: Exit to Open Positive Contactors (Functional)
if ContactorTime seconds elapse from entering the state

##### #140: Open Open Pre-Charger Contactors (Functional)
In this state set Charger Command Pre-charger Contactor = false

###### #141: Exit to Open Negative Contactors (Functional)
if ContactorTime seconds elapse from entering the state

##### #142: Open Open Negative Contactors (Functional)
In this state set Charger Command Negative Contactor = false

##### #144: Exit Conditions to Closing (Functional)
if StateRequest == Charging AND
Inverter Contactors State == Open AND
FaultPresent == False

#### #145: Closing (Functional)

##### #146: Exit Conditions to Opening (Functional)
if StateRequest != Charging OR
FaultPresent == True

##### #147: Init State (Functional)
The initial state is Open Pre-Charger Contactors.
Before to enter in this state we set Fault_out.Charger = false

##### #148: Close Negative Contactors (Functional)
In this state set Charger Command Negative Contactor = true

###### #149: Exit to Close Pre-Charger Contactors (Functional)
if ContactorTime seconds elapse from entering the state

##### #150: Close Pre-Charger Contactors (Functional)
In this state set Charger Command Pre-charger Contactor = true

###### #156: Exit Conditions and priorities (Functional)
Priory Exits:
1) Exit to Exit to Close Positive Contactors
2) Exit to Pre-Charger Fault

###### #151: Exit to Close Positive Contactors (Functional)
if (VCharger/PackVoltage) >= vratio

###### #157: Exit to Pre-Charger Fault (Functional)
if TimeoutContactor seconds elapse from entering the state

##### #152: Close Positive Contactors (Functional)
In this state set Charger Command Positive Contactor = true

###### #153: Exit to Open Pre-Charger Contactors (Functional)
if ContactorTime seconds elapse from entering the state

##### #154: Open Pre-Charger Contactors (Functional)
In this state set Charger Command Pre-charger Contactor = false

##### #155: Pre-Charger Fault (Functional)

### #158: Inverter Contactors Management (Functional)
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It is necessary close and open inverter contactors following some steps

#### #159: Opening (Functional)

##### #160: Exit Conditions to Closing (Functional)
if StateRequest == Driving AND
Charger Contactors State == Open AND
FaultPresent == False

##### #161: Init State (Functional)
The initial state is Open Pre-Charger Contactors.
Before to enter in this state we set Fault_out.Charger = false

##### #162: Close Pre-Charger Contactors (Functional)
In this state set Charger Command Pre-charger Contactor = true

###### #163: Exit to Open Positive Contactors (Functional)
if ContactorTime seconds elapse from entering the state

##### #164: Open Positive Contactors (Functional)
In this state set Charger Command Positive Contactor = false

###### #165: Exit to Open Pre-Charger Contactors (Functional)
if ContactorTime seconds elapse from entering the state

##### #166: Open Open Pre-Charger Contactors (Functional)
In this state set Charger Command Pre-charger Contactor = false

###### #167: Exit to Open Negative Contactors (Functional)
if ContactorTime seconds elapse from entering the state

##### #168: Open Open Negative Contactors (Functional)
In this state set Charger Command Negative Contactor = false

#### #169: Closing (Functional)

##### #170: Exit Conditions to Opening (Functional)
if StateRequest != Driving OR
FaultPresent == True

##### #171: Init State (Functional)
The initial state is Open Pre-Charger Contactors.
Before to enter in this state we set Fault_out.Charger = false

##### #172: Close Negative Contactors (Functional)
In this state set Charger Command Negative Contactor = true

###### #173: Exit to Close Pre-Charger Contactors (Functional)
if ContactorTime seconds elapse from entering the state

##### #174: Close Pre-Charger Contactors (Functional)
In this state set Charger Command Pre-charger Contactor = true

###### #175: Exit Conditions and priorities (Functional)
Priory Exits:
1) Exit to Exit to Close Positive Contactors
2) Exit to Pre-Charger Fault

###### #176: Exit to Close Positive Contactors (Functional)
if (VCharger/PackVoltage) >= vratio

###### #177: Exit to Pre-Charger Fault (Functional)
if TimeoutContactor seconds elapse from entering the state

##### #178: Close Positive Contactors (Functional)
In this state set Charger Command Positive Contactor = true

###### #179: Exit to Open Pre-Charger Contactors (Functional)
if ContactorTime seconds elapse from entering the state

##### #180: Open Pre-Charger Contactors (Functional)
In this state set Charger Command Pre-charger Contactor = false

##### #181: Pre-Charger Fault (Functional)
